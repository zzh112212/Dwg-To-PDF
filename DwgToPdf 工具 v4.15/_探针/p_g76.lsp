;; p_g76.lsp -- dump the Model layout record's key group codes (shade plot = 76).
;; Standalone on purpose: appending functions to an existing probe breaks its load.
;; No lambda / vl-remove-if: keep it to plain setq + entget + assoc.
(defun p_g76 ()
  (setq PT_H (open "C:/Temp/dwgtopdf_probe/g76.txt" "w"))
  (setq PT_D (dictsearch (namedobjdict) "ACAD_LAYOUT"))
  (setq PT_M (member (cons 3 "Model") PT_D))
  (write-line (strcat "member3Model=" (vl-princ-to-string PT_M)) PT_H)
  (setq PT_L (cdr (assoc 350 PT_M)))
  (write-line (strcat "layoutEname=" (vl-princ-to-string PT_L)) PT_H)
  (setq PT_LE (entget PT_L))
  (write-line (strcat "pairCount=" (itoa (length PT_LE))) PT_H)
  (write-line (strcat "g76  =" (vl-princ-to-string (cdr (assoc 76 PT_LE)))) PT_H)
  (write-line (strcat "g70  =" (vl-princ-to-string (cdr (assoc 70 PT_LE)))) PT_H)
  (write-line (strcat "g146 =" (vl-princ-to-string (cdr (assoc 146 PT_LE)))) PT_H)
  (write-line (strcat "g4   =" (vl-princ-to-string (cdr (assoc 4 PT_LE)))) PT_H)
  (write-line (strcat "g2   =" (vl-princ-to-string (cdr (assoc 2 PT_LE)))) PT_H)
  (write-line (strcat "g48  =" (vl-princ-to-string (cdr (assoc 48 PT_LE)))) PT_H)
  (write-line (strcat "g140 =" (vl-princ-to-string (cdr (assoc 140 PT_LE)))) PT_H)
  (close PT_H))
