;; p_compare.lsp -- one-shot plot / lineweight / transparency comparison dump.
;; ASCII only. Writes to the handle PT_FH opened by the caller .scr.
;; Read-only: entget / tblnext / dictsearch only. No write to the DWG.
;;
;; Call contract (.scr):
;;   (setq PT_FH (open "C:/Temp/dwgtopdf_probe/out_plotcfg.txt" "w"))
;;   (load "C:/Temp/dwgtopdf_probe/p_compare.lsp")
;;   (setq PT_R (vl-catch-all-apply 'p_all nil))
;;   (close PT_FH)

(defun _o (s) (write-line s PT_FH))

(defun _g (name / r)
  (setq r (vl-catch-all-apply 'getvar (list name)))
  (cond ((vl-catch-all-error-p r) "<ERR>")
        ((null r) "<nil>")
        ((= (type r) 'STR) r)
        ((= (type r) 'REAL) (rtos r 2 6))
        (T (itoa (atoi (rtos r 2 0))))))

(defun _v2s (v)
  (cond ((null v) "")
        ((= (type (cdr v)) 'STR) (cdr v))
        ((= (type (cdr v)) 'REAL) (rtos (cdr v) 2 6))
        ((= (type (cdr v)) 'INT) (itoa (cdr v)))
        (T (vl-princ-to-string (cdr v)))))

(defun _bits (val / v i a out)
  (if (not (numberp val))
    (strcat "<non-numeric: " (vl-princ-to-string val) ">")
    (progn
      (setq v (atoi (rtos val 2 0)) out "" i 0)
      (while (< i 24)
        (setq a (fix (/ v (expt 2 i))))
        (if (= 1 (- a (* 2 (fix (/ a 2)))))
          (setq out (strcat out "+" (itoa (expt 2 i)) " ")))
        (setq i (1+ i)))
      (strcat (itoa v) " [" out "]"))))

(defun _bump (key alist / hit)
  (if (setq hit (assoc key alist))
    (subst (cons key (1+ (cdr hit))) hit alist)
    (append alist (list (cons key 1)))))

(defun _ph (tag alist)
  (if (null alist)
    (_o (strcat tag " <none>"))
    (foreach kv alist
      (_o (strcat tag " " (car kv) " x" (itoa (cdr kv)))))))

(defun _rec2p (x)
  (and (listp x) (listp (car x)) (= (car (car x)) 2)))

(defun _layerrecords (/ r out rec)
  (setq out nil)
  (setq r (vl-catch-all-apply 'tblnext (list "LAYER" T)))
  (if (not (vl-catch-all-error-p r))
    (progn
      (if (_rec2p r)
        (setq out (list r))
        (foreach rec r (if (_rec2p rec) (setq out (append out (list rec))))))))
  out)

(defun _llist (/ d r lst out)
  (setq out nil)
  (setq r (vl-catch-all-apply 'dictsearch (list (namedobjdict) "ACAD_LAYOUT")))
  (if (not (vl-catch-all-error-p r))
    (progn
      (setq d r)
      (foreach lst (cdr d)
        (if (= (car lst) 3) (setq out (cons (cdr lst) out))))))
  (reverse out))

(defun _layobj (nm / r lst)
  (setq r (vl-catch-all-apply 'dictsearch (list (namedobjdict) "ACAD_LAYOUT")))
  (if (vl-catch-all-error-p r)
    nil
    (progn
      (setq lst (member (cons 3 nm) r))
      (if lst (cdr (assoc 350 lst)) nil))))

(defun p_layouts (/ nm lay e v)
  (foreach nm (_llist)
    (setq lay (_layobj nm))
    (_o (strcat "LAYOUT " nm))
    (if (null lay)
      (_o "   NOT FOUND")
      (progn
        (setq e (entget lay))
        (foreach c '(2 4 7 70 72 73 74 76 146 40 41 42 43 44 45 46 47 48 140 147)
          (setq v (assoc c e))
          (if v (_o (strcat "   g" (itoa c) " = " (_v2s v)))))
        (setq v (assoc 70 e))
        (if v (_o (strcat "   >> g70bits " (_bits (cdr v)))))))))

(defun _inset (lst nm)
  (member nm lst))

(defun _layerrecords2 (/ r cnt out)
  ;; MEASURED: (tblnext "LAYER" T) DOES work; an earlier filter wrongly required the
  ;; first pair to be (2 . name) but a layer record starts with (0 . "LAYER").
  (setq out nil cnt 0)
  (setq r (vl-catch-all-apply 'tblnext (list "LAYER" T)))
  (while (and r (not (vl-catch-all-error-p r)) (< cnt 300))
    (setq cnt (1+ cnt))
    (setq out (append out (list r)))
    (setq r (vl-catch-all-apply 'tblnext (list "LAYER"))))
  out)

(defun p_all (/ ss i n e ty lay lw tr cl sp
                tyH lwMH lwPH lwCURV trMH trH clH layH
                n370m nNo370m n370p nNo370p n440m tot)
  (terpri)
  (_o "===== COMPARE DUMP =====")
  (_o (strcat "DWGPREFIX = " (_g "DWGPREFIX")))
  (_o (strcat "SYSVAR ACADVER = " (_g "ACADVER")))
  (_o (strcat "SYSVAR LWDEFAULT = " (_g "LWDEFAULT")))
  (_o (strcat "SYSVAR LWDISPLAY = " (_g "LWDISPLAY")))
  (_o (strcat "SYSVAR CECOLOR = " (_g "CECOLOR")))
  (_o (strcat "SYSVAR CELWEIGHT = " (_g "CELWEIGHT")))
  (_o (strcat "SYSVAR PSTYLEMODE = " (_g "PSTYLEMODE")))
  (_o (strcat "SYSVAR INSUNITS = " (_g "INSUNITS")))
  (_o (strcat "SYSVAR MEASUREMENT = " (_g "MEASUREMENT")))
  (_o (strcat "SYSVAR CTAB = " (_g "CTAB") " / TILEMODE = " (_g "TILEMODE")))
  (terpri)
  (p_layouts)
  (terpri)
  (_o "----- LAYER TABLE -----")
  (setq layH (_layerrecords2))
  (if (null layH)
    (_o "  <layer table unreadable>")
    (foreach rec layH
      (_o (strcat "LAYER " (vl-princ-to-string (cdr (assoc 2 rec)))
                  " | c62=" (vl-princ-to-string (cdr (assoc 62 rec)))
                  " | g370=" (vl-princ-to-string (cdr (assoc 370 rec)))
                  " | g70=" (vl-princ-to-string (cdr (assoc 70 rec)))))))
  (terpri)
  (_o "----- ENTITY PASS (whole database) -----")
  (setq ss (vl-catch-all-apply 'ssget (list "_X")))
  (if (vl-catch-all-error-p ss) (setq ss nil))
  (if (null ss)
    (_o "SSGET_X = <none or error>")
    (progn
      (_o (strcat "SSGET_X TOTAL = " (itoa (sslength ss))))
      (setq i 0 tot 0 n370m 0 nNo370m 0 n370p 0 nNo370p 0 n440m 0)
      (while (< i (sslength ss))
        (setq e (entget (ssname ss i)))
        (setq ty (cdr (assoc 0 e)))
        (setq lay (cdr (assoc 8 e)))
        (setq lw (assoc 370 e))
        (setq tr (assoc 440 e))
        (setq cl (cdr (assoc 62 e)))
        (setq sp (cdr (assoc 67 e)))
        (setq tyH (_bump ty tyH))
        (setq layH (_bump (if lay lay "<nil>") layH))
        (setq clH (_bump (if cl (itoa cl) "<none>") clH))
        (if (= sp 1)
          (progn
            (if lw (setq n370p (1+ n370p)) (setq nNo370p (1+ nNo370p))))
          (progn
            (if lw (setq n370m (1+ n370m)) (setq nNo370m (1+ nNo370m)))
            (setq lwMH (_bump (if lw (_v2s lw) "NO_370") lwMH))
            (if (member ty '("LINE" "LWPOLYLINE" "POLYLINE" "ARC" "CIRCLE" "ELLIPSE" "SPLINE"))
              (setq lwCURV (_bump (if lw (_v2s lw) "NO_370") lwCURV)))
            (if tr
              (progn (setq n440m (1+ n440m))
                     (setq trMH (_bump (_v2s tr) trMH))))))
        (setq i (1+ i)))
      (terpri)
      (_o "----- TYPE HISTOGRAM -----")
      (_ph "TYPE" tyH)
      (terpri)
      (_o "----- ENTITY LINE WEIGHT g370 (MODEL space) -----")
      (_o (strcat "MODEL with370 = " (itoa n370m) " / without370 = " (itoa nNo370m)))
      (_o (strcat "PAPER with370 = " (itoa n370p) " / without370 = " (itoa nNo370p)))
      (_ph "G370M" lwMH)
      (terpri)
      (_o "----- CURVE-TYPE g370 (MODEL space) -----")
      (_ph "G370CURV" lwCURV)
      (terpri)
      (_o "----- ENTITY TRANSPARENCY g440 (MODEL space) -----")
      (_o (strcat "MODEL entities with440 = " (itoa n440m)))
      (_ph "G440M" trMH)
      (terpri)
      (_o "----- ENTITY COLOR g62 (MODEL+ALL) -----")
      (_ph "G62" clH)
      (terpri)
      (_o "----- ENTITY LAYER g8 (MODEL+ALL) -----")
      (_ph "G8" layH)))
  (terpri)
  (_o "===== END =====")
  (terpri))

(princ)
